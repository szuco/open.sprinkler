# -*- coding: utf-8 -*-
"""
OpenSprinkler Design-Abdeckhaube (2-teilig, parametrisch)
=========================================================

Erzeugt eine dekorative Haube, die von vorn ueber den *fertig an der Wand
montierten* OpenSprinkler gestuelpt wird und Gehaeuse, Klemmleisten,
Kabelbaum und Wanddurchbruch komplett verdeckt.

Teile:
  1. CoverFrame  - Rahmen/Haube (Druck: Frontseite auf dem Druckbett,
                   keine Stuetzen noetig)
  2. FrontPlate  - Frontplatte mit erhabenem "OpenSprinkler"-Relief
                   (Druck: flach, Schrift nach oben)

Die Frontplatte wird nach dem Druck von hinten in den Falz des Rahmens
geklebt (1,5 mm Schattenfuge zur Rahmenkante).

Aufhaengung: Die Haube haengt mit zwei langen Innenrippen auf der Oberseite
des Gehaeuses und liegt hinten an der Wand an - werkzeuglos, keine neuen
Loecher in der Wand.

Die Groesse wird ueber drei Mindestmasse gesteuert (Block MINDESTMASSE):
lichte Breite, Abdeckung nach unten und lichte Tiefe. Die Zugaben darunter
werden auf diese Mindestmasse aufgeschlagen - die geforderten Werte sind
also garantiert eingehalten.

Verwendung:
  - In FreeCAD:  Makro -> Makros... -> ausfuehren, oder
  - Headless:    freecadcmd OpenSprinklerCover.FCMacro
"""

import os
import FreeCAD as App
import Part
from FreeCAD import Vector

# =========================================================================
# PARAMETER (alle Angaben in mm)
# =========================================================================

# --- MINDESTMASSE (am montierten Geraet gemessen) ------------------------
# Beschreiben den Raum, den die Haube ueberdecken muss - nicht die Haube
# selbst. Die Haube faellt entsprechend groesser aus.
CLEAR_W    = 170.0  # min. lichte Breite = Breite der montierten Einheit
CLEAR_DROP = 160.0  # min. Abdeckung ab Oberkante Geraet nach unten
                    # (Gehaeuse + Klemmen + Kabel + Wandoeffnung)
CLEAR_D    = 25.0   # min. lichte Tiefe: Wand -> Frontflaeche des Geraetes

# --- Zugaben auf die Mindestmasse ----------------------------------------
ADD_W      = 5.0   # zusaetzliches Spiel je Seite (deckt seitlich
                   # ueberstehende Klemmverbinder / abgehende Kabel ab)
ADD_DROP   = 5.0   # zusaetzliche Abdeckung nach unten
ADD_D      = 7.0   # zusaetzliche Tiefe (Kabelbogen aus der Wand, Toleranz).
                   # Zu tief = Haube steht etwas weiter vor (harmlos).
                   # Zu flach = hinterer Rand liegt nicht an der Wand an.

CASE_H     = 100.0 # nur informativ: Hoehe des Geraetekoerpers ohne Klemmen,
                   # wird nur fuer die Ausgabe am Ende verwendet

# --- Haube ---------------------------------------------------------------
RIB_H        = 2.0   # Hoehe der Auflagerippen (Haube haengt damit auf dem
                     # Gehaeuse; groesser = Haube sitzt hoeher)
RIB_X        = 52.0  # Abstand der Auflagerippen von der Mitte
RIB_W        = 4.0   # Breite der Auflagerippen
WALL         = 3.0   # Wandstaerke
R_OUT        = 8.0   # Aussenradius der senkrechten Kanten
R_IN         = 5.0   # Innenradius (Falz / Frontplatte)
CHAMFER_F    = 1.5   # Fase an der vorderen Aussenkante
SEAT_DEPTH   = 4.5   # Falztiefe fuer die Frontplatte
LEDGE        = 2.0   # Auflagesteg-Breite fuer die Frontplatte (oben+unten)
BACK_GAP     = 0.5   # Luft zwischen Gehaeuserueckseite und Wandanlage
CRIB_TOP_OFF = 8.0   # Zentrierrippen hinten: Abstand von der Geraeteoberkante
CRIB_LEN     = 52.0  # Laenge der Zentrierrippen (bleiben im oberen Bereich,
                     # damit sie unten abgehende Kabel nicht beruehren)

# --- Frontplatte ---
PLATE_T      = 3.0   # Plattendicke
PLATE_CLEAR  = 0.25  # Spiel Platte <-> Falz (pro Seite)

# --- Relief-Schriftzug ---
TEXT         = "OpenSprinkler"
TEXT_SIZE    = 15.0  # Schriftgroesse
TEXT_RELIEF  = 1.4   # Erhabenheit des Reliefs
TEXT_STYLE   = "raised"   # "raised" = erhaben, "engraved" = vertieft
TEXT_Y_OFF   = 0.0   # Schriftzug aus der Plattenmitte verschieben (+ = hoch)
FONT_CANDIDATES = [
    "/System/Library/Fonts/Supplemental/Arial Rounded Bold.ttf",  # macOS
    "/System/Library/Fonts/Supplemental/Verdana Bold.ttf",        # macOS
    "/System/Library/Fonts/Supplemental/Arial Bold.ttf",          # macOS
    "C:/Windows/Fonts/ARLRDBD.TTF",                               # Windows
    "C:/Windows/Fonts/verdanab.ttf",                              # Windows
    "C:/Windows/Fonts/arialbd.ttf",                               # Windows
    "/usr/share/fonts/truetype/dejavu/DejaVuSans-Bold.ttf",       # Linux
]
FONT = ""            # optional: eigenen Font-Pfad hier fest eintragen

# --- Lueftung / Kabel ---
VENT_SLOTS     = 6     # Anzahl Lueftungsschlitze oben und unten (0 = keine)
VENT_L         = 20.0  # Schlitzlaenge
VENT_W         = 4.0   # Schlitzbreite
VENT_PITCH_GAP = 6.0   # Steg zwischen zwei Schlitzen
CABLE_SLOT_W   = 150.0 # Breite des Kabelschlitzes unten hinten
CABLE_SLOT_D   = 16.0  # Tiefe des Kabelschlitzes (von der Wand aus)

# --- Export ---
EXPORT = True        # STL + FCStd neben dem Makro ablegen

# =========================================================================
# ABGELEITETE MASSE
# =========================================================================

IN_W    = CLEAR_W + 2 * ADD_W               # lichte Breite
DROP    = CLEAR_DROP + ADD_DROP             # Abdeckung ab Geraeteoberkante
INNER_D = CLEAR_D + ADD_D                   # lichte Tiefe
IN_H    = RIB_H + DROP                      # Innenhoehe Kavitaet

SEAT_W = IN_W                               # Falz = vordere Oeffnung
SEAT_H = IN_H + 2 * LEDGE
OUT_W  = IN_W + 2 * WALL                    # Aussenmasse
OUT_H  = SEAT_H + 2 * WALL
DEPTH  = SEAT_DEPTH + INNER_D + BACK_GAP

xi, yi = IN_W / 2.0, IN_H / 2.0             # Kavitaet-Halbmasse
xs, ys = SEAT_W / 2.0, SEAT_H / 2.0         # Falz-Halbmasse
xo, yo = OUT_W / 2.0, OUT_H / 2.0           # Aussen-Halbmasse

Y_CASE_TOP = yi - RIB_H                     # Oberkante des Geraetes
Z_WALL     = DEPTH - BACK_GAP               # Ebene der Wand

PLATE_W = SEAT_W - 2 * PLATE_CLEAR
PLATE_H = SEAT_H - 2 * PLATE_CLEAR
PLATE_R = R_IN - PLATE_CLEAR

# =========================================================================
# HILFSFUNKTIONEN
# =========================================================================

def rounded_box(w, h, d, r):
    """Quader (zentriert in X/Y, z=0..d) mit verrundeten senkrechten Kanten."""
    b = Part.makeBox(w, h, d)
    b.translate(Vector(-w / 2.0, -h / 2.0, 0))
    edges = []
    for e in b.Edges:
        v0, v1 = e.Vertexes[0].Point, e.Vertexes[1].Point
        if abs(v0.x - v1.x) < 1e-6 and abs(v0.y - v1.y) < 1e-6:
            edges.append(e)
    return b.makeFillet(r, edges)


def vent_spans():
    """x-Bereiche der Lueftungsschlitze."""
    if VENT_SLOTS <= 0:
        return []
    pitch = VENT_L + VENT_PITCH_GAP
    x0 = -(VENT_SLOTS * pitch - VENT_PITCH_GAP) / 2.0
    return [(x0 + i * pitch, x0 + i * pitch + VENT_L) for i in range(VENT_SLOTS)]


def find_font():
    if FONT and os.path.exists(FONT):
        return FONT
    for f in FONT_CANDIDATES:
        if os.path.exists(f):
            return f
    return None


def make_text_shape(doc, font):
    """Erzeugt den Schriftzug als flaches Face-Compound in der XY-Ebene."""
    import Draft
    try:
        obj = Draft.make_shapestring(TEXT, font, TEXT_SIZE)
    except AttributeError:  # aeltere FreeCAD-Versionen
        obj = Draft.makeShapeString(TEXT, font, TEXT_SIZE)
    doc.recompute()
    shape = obj.Shape.copy()
    doc.removeObject(obj.Name)
    return shape


# =========================================================================
# TEIL 1: RAHMEN / HAUBE
# =========================================================================

frame = rounded_box(OUT_W, OUT_H, DEPTH, R_OUT)

# Durchgehende Kavitaet in Falzgroesse -> offener Rahmen (Tube)
cavity = rounded_box(SEAT_W, SEAT_H, DEPTH + 2, R_IN)
cavity.translate(Vector(0, 0, -1))
frame = frame.cut(cavity)

# Auflagestege oben + unten (bilden den Falz fuer die Frontplatte und
# verengen die Kavitaet auf IN_H). 45-Grad-Fase an der Vorderkante,
# damit der Rahmen ohne Stuetzen mit der Front nach unten druckbar ist.
bar_len = 2 * (xs - R_IN)
for sign in (+1, -1):
    bar = Part.makeBox(bar_len, LEDGE, DEPTH - SEAT_DEPTH)
    y0 = yi if sign > 0 else -ys
    bar.translate(Vector(-bar_len / 2.0, y0, SEAT_DEPTH))
    y_edge = yi if sign > 0 else -yi
    for e in bar.Edges:
        v0, v1 = e.Vertexes[0].Point, e.Vertexes[1].Point
        if (abs(v0.z - SEAT_DEPTH) < 1e-6 and abs(v1.z - SEAT_DEPTH) < 1e-6
                and abs(v0.y - y_edge) < 1e-6 and abs(v1.y - y_edge) < 1e-6):
            bar = bar.makeChamfer(LEDGE * 0.9, [e])
            break
    frame = frame.fuse(bar)

frame = frame.removeSplitter()

# Kabelschlitz unten hinten (falls doch eine Leitung nach unten/hinten aus
# der Haube heraus muss; dient zugleich als Lueftungsoeffnung)
slot = Part.makeBox(CABLE_SLOT_W, 12.0, CABLE_SLOT_D + 2)
slot.translate(Vector(-CABLE_SLOT_W / 2.0, -yo - 2.0, DEPTH - CABLE_SLOT_D))
frame = frame.cut(slot)

# Lueftungsschlitze (von vorn unsichtbar): unten vorn = Einlass,
# oben hinten = Auslass
if VENT_SLOTS > 0:
    cuts = []
    for a, b in vent_spans():
        v = Part.makeBox(b - a, 8.0, VENT_W)           # unten
        v.translate(Vector(a, -yo - 1.5, 12.0))
        cuts.append(v)
        v = Part.makeBox(b - a, 8.0, VENT_W)           # oben
        v.translate(Vector(a, yi - 0.5, DEPTH - 16.0))
        cuts.append(v)
    frame = frame.cut(Part.makeCompound(cuts))

# Auflagerippen an der Deckenwand: die Haube haengt damit auf dem Gehaeuse.
# Sie laufen fast ueber die gesamte Tiefe, damit sie das Gehaeuse auch dann
# sicher treffen, wenn die Tiefe grosszuegig geschaetzt wurde. Sie werden
# erst nach den Schlitzen angebaut und liegen in den Stegen zwischen zwei
# Lueftungsschlitzen.
RIB_Z0 = SEAT_DEPTH + 3.0
RIB_Z1 = DEPTH - 4.0
for x in (-RIB_X, RIB_X):
    for a, b in vent_spans():
        if x + RIB_W / 2.0 > a and x - RIB_W / 2.0 < b:
            App.Console.PrintWarning(
                "Auflagerippe bei x=%.1f liegt unter einem Lueftungsschlitz "
                "- RIB_X anpassen.\n" % x)
            break
    rib = Part.makeBox(RIB_W, RIB_H, RIB_Z1 - RIB_Z0)
    rib.translate(Vector(x - RIB_W / 2.0, yi - RIB_H, RIB_Z0))
    frame = frame.fuse(rib)

# Seitliche Zentrierrippen hinten (fuehren die Haube an den Montagelaschen).
# Bewusst nur im oberen Bereich, damit sie seitlich abgehende Kabel oder
# Klemmverbinder im unteren Bereich nicht beruehren.
rib_t = min(ADD_W - 0.55, 3.0)
cr_y1 = Y_CASE_TOP - CRIB_TOP_OFF
cr_y0 = cr_y1 - CRIB_LEN
for sign in (+1, -1):
    rib = Part.makeBox(rib_t + 0.01, CRIB_LEN, 8.0)
    x0 = xi - rib_t if sign > 0 else -xi - 0.01
    rib.translate(Vector(x0, cr_y0, DEPTH - 12.0))
    frame = frame.fuse(rib)

frame = frame.removeSplitter()

# Fase an der vorderen Aussenkante (Optik) + kleine Fase am Falzrand
front_outer, front_inner = [], []
for e in frame.Edges:
    bb = e.BoundBox
    if bb.ZMax < 1e-4:
        if (bb.XMax > xs + 1 or bb.XMin < -(xs + 1)
                or bb.YMax > ys + 1 or bb.YMin < -(ys + 1)):
            front_outer.append(e)
        else:
            front_inner.append(e)
frame = frame.makeChamfer(CHAMFER_F, front_outer)
front_inner = [e for e in frame.Edges if e.BoundBox.ZMax < 1e-4
               and e.BoundBox.XMax < xs + 1 and e.BoundBox.XMin > -(xs + 1)
               and e.BoundBox.YMax < ys + 1 and e.BoundBox.YMin > -(ys + 1)]
if front_inner:
    frame = frame.makeChamfer(0.5, front_inner)

# =========================================================================
# TEIL 2: FRONTPLATTE MIT RELIEF
# =========================================================================

plate = rounded_box(PLATE_W, PLATE_H, PLATE_T, PLATE_R)

# dekorative Fase an der oberen Aussenkante
top_edges = [e for e in plate.Edges if e.BoundBox.ZMin > PLATE_T - 1e-4]
plate = plate.makeChamfer(0.6, top_edges)

doc = App.newDocument("OpenSprinklerCover")

font = find_font()
if font:
    text_faces = make_text_shape(doc, font)
    bb = text_faces.BoundBox
    # Breite begrenzen, falls der Font sehr breit laeuft
    max_w = PLATE_W - 30.0
    if bb.XLength > max_w:
        s = max_w / bb.XLength
        m = App.Matrix()
        m.scale(s, s, 1.0)
        text_faces = text_faces.transformGeometry(m)
        bb = text_faces.BoundBox
    # zentrieren
    text_faces.translate(Vector(-bb.XMin - bb.XLength / 2.0,
                                -bb.YMin - bb.YLength / 2.0 + TEXT_Y_OFF, 0))
    if TEXT_STYLE == "engraved":
        text_faces.translate(Vector(0, 0, PLATE_T - TEXT_RELIEF))
        text_solid = text_faces.extrude(Vector(0, 0, TEXT_RELIEF + 1))
        plate = plate.cut(text_solid)
    else:
        text_faces.translate(Vector(0, 0, PLATE_T))
        text_solid = text_faces.extrude(Vector(0, 0, TEXT_RELIEF))
        plate = plate.fuse(text_solid)
    plate = plate.removeSplitter()
else:
    App.Console.PrintWarning(
        "Kein Font gefunden - Platte ohne Schriftzug erzeugt. "
        "Bitte FONT im Makro auf eine .ttf-Datei setzen.\n")

# =========================================================================
# DOKUMENT AUFBAUEN (Zusammenbau-Ansicht)
# =========================================================================

frame_obj = doc.addObject("Part::Feature", "CoverFrame")
frame_obj.Shape = frame

plate_obj = doc.addObject("Part::Feature", "FrontPlate")
plate_obj.Shape = plate
# eingebaut: um 180 Grad gedreht, Relief zeigt nach vorn (-Z),
# Rueckseite liegt auf dem Falz bei z = SEAT_DEPTH
plate_obj.Placement = App.Placement(
    Vector(0, 0, SEAT_DEPTH), App.Rotation(Vector(0, 1, 0), 180))

if App.GuiUp:
    frame_obj.ViewObject.ShapeColor = (0.35, 0.55, 0.35)   # salbeigruen
    plate_obj.ViewObject.ShapeColor = (0.92, 0.90, 0.85)   # cremeweiss

doc.recompute()

# =========================================================================
# EXPORT
# =========================================================================

if EXPORT:
    try:
        out_dir = os.path.dirname(os.path.abspath(__file__))
    except NameError:
        out_dir = os.path.join(os.path.expanduser("~"),
                               "OpenSprinklerCover_Export")
        os.makedirs(out_dir, exist_ok=True)

    doc.saveAs(os.path.join(out_dir, "OpenSprinklerCover.FCStd"))

    def export_stl(shape, path):
        try:
            import MeshPart
            m = MeshPart.meshFromShape(Shape=shape, LinearDeflection=0.1,
                                       AngularDeflection=0.35)
            m.write(path)
        except Exception:
            shape.exportStl(path)

    # Rahmen: liegt bereits druckgerecht (Front unten, Oeffnung oben)
    export_stl(frame, os.path.join(out_dir, "CoverFrame.stl"))
    # Platte: druckgerecht flach, Relief nach oben
    export_stl(plate, os.path.join(out_dir, "FrontPlate.stl"))

    App.Console.PrintMessage("Export nach %s abgeschlossen.\n" % out_dir)

App.Console.PrintMessage(
    "Haube aussen  : %.1f x %.1f x %.1f mm (B x H x T)\n"
    % (OUT_W, OUT_H, DEPTH))
App.Console.PrintMessage(
    "Lichte Weite  : %.1f mm  (gefordert min. %.1f)\n" % (IN_W, CLEAR_W))
App.Console.PrintMessage(
    "Abdeckung ab Oberkante nach unten: %.1f mm  (gefordert min. %.1f)\n"
    % (DROP, CLEAR_DROP))
App.Console.PrintMessage(
    "Lichte Tiefe  : %.1f mm  (gefordert min. %.1f)\n" % (INNER_D, CLEAR_D))
App.Console.PrintMessage(
    "davon unter der Geraeteunterkante (bei CASE_H=%.0f): %.1f mm\n"
    % (CASE_H, DROP - CASE_H))
App.Console.PrintMessage(
    "Druckbett     : mind. %.0f x %.0f mm\n" % (OUT_W + 4, OUT_H + 4))
